FME workspace Extract Single Jobs from GSPP.fmw

Parameters:
- BASEURL =
- DestDataset_SHAPEFILE =
- FME_USER_PARAM_PRIVATE_GRP =
- JOBSENDPOINT =
- SourceDataset_XLSXR =

Readers:
- XLSXR_1: XLSXR from $(SourceDataset_XLSXR)

Writers:
- SHAPEFILE_1: SHAPEFILE to $(DestDataset_SHAPEFILE)

Note: Before running ensure the FeatureReader has your web connection details for the GSPP MI API. / - Open Feature Reader / - Select Parameters / - Under web connection exchange for your PR2A connection
Note: 1. Add list of Job IDs to spreadsheet
Note: 2. Press Play
Note: 3. Enter Shapefile output destination as required

Bookmark: Spreadsheet list of job ids
Sheet1 (reader XLSXR_1)
    attributes: jobId number(7,0)
    -> FeatureReader [INITIATOR]

Bookmark: queries job endpoint
FeatureReader
    ATTRS_TO_EXPOSE = activityTags aoiArea captureMethod closedDate creationDate currentAssignment earliestStartDate eastings editStartDate flowlineCode jobAllocation jobDescription jobId jobTypeName json_type lastStatusUpdate latestEndDate northings operationalPriority planningItemId priority productionGroupAssignment reasonForChange scheduledEndDate scheduledStartDate siNumber status updateType
    ATTR_ACCUM_MODE = Only Use Result
    COMBINE_GEOM = Use Result
    DATASET = https://gspppr2amanagementinformation.azure-api.net/api/v2/jobs/@Value(jobId)
    FORMAT = JSON
    JSON_COORDINATE_SYSTEM_KEY = OSGB-GPS-2015-OSTN15
    JSON_DECODE_TEXT_STRINGS = Yes
    JSON_FEATURE_TYPE_KEY = json_featuretype
    JSON_FLATTEN_MODE = ALL_LEVELS
    JSON_GEOMETRY_FORMAT = OGC-WKT
    JSON_GEOMETRY_KEY = aoiGeometry
    JSON_NETWORK_AUTHENTICATION = AUTH_INFO_GROUP,YES,AUTH_METHOD,Named Web Connection,NAMED_CONNECTION,kharvey PR2A Management Information API,AUTH_USERNAME,<Unused>,AUTH_PASSWORD,<Unused>
    JSON_SAVE_FRAGMENTS = NO
    JSON_SCAN_MODE = AUTO
    JSON_USE_BASENAME_AS_DEFAULT_FEATURE_TYPE = No
    JSON_USE_SEARCH_ENVELOPE = NO
    OUTPUT_FEATURES_DISPLAY = Schema and Data Features
    <OTHER> -> Shapefile1 (writer SHAPEFILE_1)

Bookmark: Output shapefile
Shapefile1 (writer SHAPEFILE_1)
    attributes: activityTa varchar(200), aoiArea varchar(200), captureMet varchar(200), closedDate varchar(200), creationDa varchar(200), currentAss varchar(200), earliestSt varchar(200), eastings varchar(200), editStartD varchar(200), flowlineCo varchar(200), jobAllocat varchar(200), jobDescrip varchar(200), jobId varchar(200), jobTypeNam varchar(200), json_type varchar(200), lastStatus varchar(200), latestEndD varchar(200), northings varchar(200), operationa varchar(200), planningIt varchar(200), priority varchar(200), production varchar(200), reasonForC varchar(200), scheduledE varchar(200), scheduledS varchar(200), siNumber varchar(200), status varchar(200), updateType varchar(200)
